module hello {
    yang-version 1;
    namespace "urn:opendaylight:params:xml:ns:yang:hello";
    prefix "hello";

    import yang-ext {prefix ext; revision-date "2013-07-09";}

    revision "2015-01-05" {
        description "Initial revision of hello model";
    }
        
    rpc hello-world {
            input {
                    leaf strin {
                            type string;
                    }
            }
            output {
                    leaf greating {
                            type string;
                    }
            }
    }
    
    rpc noinput-output {
            description "no input and output rpc";
    }    
    
    container helloWorld {                
        leaf counter {        
                type uint32;
                config true;
                default 100;
        }        
                
        leaf value {        
                type string;
                config false;
                mandatory false;
        }        
	}  
    
    grouping fish {
    	leaf fish-id {
    		type uint32;
    	}
    	leaf fish-name {
    		type string;
    	}
    }
    
    grouping mammal {
    	leaf mammal-id {
    		type uint32;
    	}
    	leaf mammal-name {
    		type string;
    	}
    }
    
    grouping animal {
    	list "fish" {
    		key "fish-id";
    		uses fish;
    	}
    	
    	list "mammal" {
    		key "mammal-id";
    		uses mammal;
    	}
    	
    }
    
    container organism {
    	uses animal;
    }

    rpc animal-write {
        input {
        		leaf id {
        			type uint32;
        		}
                leaf strin {
                       type string;
                }
        }
        output {
                leaf strout {
                       type string;
                }
        }
	}
    
    rpc hello-world-write {
        input {
                leaf strin {
                       type string;
                }
        }
        output {
                leaf strout {
                       type string;
                }
        }
	}

	rpc hello-world-read {
        input {
                leaf strin {
                        type string;
                }
        }
        output {
                leaf strout {
                        type string;
                }
        }
	}
	
    notification multipleOfTens {
        description
        "indicates that the counter has reached multiple of 10.";
	}

	    typedef cat-ref {
            type instance-identifier;
            description "A reference that points to a cat in the data tree.";
        }

        identity cat-context {
            description "A cat-context is a classifier for node elements which allows an RPC to provide a service on behalf of a particular element in the data tree.";
        }

        grouping cat {
            leaf name {
                type string;
            }
            container paw {
                leaf name {
                type string;
                }
            }
        }

        container cats {
            description "The root container of all nodes.";
            list cat {
                key "name";
                ext:context-instance name;
                uses cat;
            }
        }

        rpc make-sound {
            input {
            		leaf name-ref {
            		    //type string;
                    	ext:context-reference cat-context;
                    	type cat-ref;
                	}
            }

            output {
                    leaf result {
                        type string;
                    }
            }

        }

}
